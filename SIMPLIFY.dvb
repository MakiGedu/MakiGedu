Attribute VB_Name = "UserForm1"
Attribute VB_Base = "0{305DA434-BA17-4F1E-AB7C-F6E301E3B4FA}{B7AE0633-F404-4CB7-AD03-553F0FC64B45}"
Attribute VB_GlobalNameSpace = False
Attribute VB_Creatable = False
Attribute VB_PredeclaredId = True
Attribute VB_Exposed = False
Attribute VB_TemplateDerived = False
Attribute VB_Customizable = False
 
Dim Depth As Double
Dim Width As Double
Dim ConcreteCover As Double


Private Sub ColumnExport_Click()

End Sub

Private Sub date_no_Exit(ByVal Cancel As MSForms.ReturnBoolean)
 If Not IsDate(date_no.Text) Then
        MsgBox "A valid Date required"
        Cancel = True
    End If
End Sub

Private Sub BeamExport_Click()

Dim Execl As New Excel.Application
Dim workbk As Excel.Workbook
Dim Excelworksheet As Worksheet
Dim ExcelworksheetTwo As Worksheet
Dim ExcelworksheetThree As Worksheet

Dim MyArray() As String, Mystring As String
Dim tsep As Variant
Dim k As Integer
    Execl.Visible = True
Set workbk = Execl.Workbooks.Add
Set Excelworksheet = workbk.Worksheets(1)
       UserForm1.Hide
    
Excelworksheet.Cells(1, 1).Value = company
On Error GoTo Here
Excelworksheet.Cells(2, 1).Value = project
Excelworksheet.Cells(3, 1).Value = "concrete work"
Excelworksheet.Cells(4, 1).Value = "Site_No"
Excelworksheet.Cells(4, 2).Value = site
Excelworksheet.Cells(4, 6).Value = "Date"
Excelworksheet.Cells(4, 7).Value = date_no
Excelworksheet.Cells(6, 1).Value = "Timising"
Excelworksheet.Cells(6, 2).Value = "dimension"
Excelworksheet.Cells(6, 3).Value = "square"
Excelworksheet.Cells(6, 4).Value = "Describtion"
Excelworksheet.Cells(8, 4).Value = "Total volume (m^3)"

  Excelworksheet.Activate
With Excelworksheet.Range(Cells(6, 1), Cells(8, 6)).Borders
On Error GoTo Here
    .LineStyle = lxcontinuous
    .Weight = xlThin
    .color = black
End With
Dim z As Integer
For z = 1 To 3
   With Excelworksheet.Range(Cells(z, 1), Cells(z, 6))
    .HorizontalAlignment = xlCenter
    .VerticalAlignment = xlCenter
    .Merge
    .Font.Size = 16
    .Font.Name = "Times new roman"
    .Font.Bold = True
    .WrapText = True
    End With
Next z

With ActiveWindow
.SplitColumn = 0
.SplitRow = 6
End With
ActiveWindow.FreezePanes = True

'Formwork Excel Sheet
Set ExcelworksheetTwo = workbk.Worksheets.Add
ExcelworksheetTwo.Activate
ExcelworksheetTwo.Cells(1, 1).Value = company
ExcelworksheetTwo.Cells(2, 1).Value = project
ExcelworksheetTwo.Cells(3, 1).Value = "formwork"
ExcelworksheetTwo.Cells(4, 1).Value = "Site_No"
ExcelworksheetTwo.Cells(4, 2).Value = site
ExcelworksheetTwo.Cells(4, 6).Value = "Date"
ExcelworksheetTwo.Cells(4, 7).Value = date_no
ExcelworksheetTwo.Cells(6, 1).Value = "Timising"
ExcelworksheetTwo.Cells(6, 2).Value = "dimension"
ExcelworksheetTwo.Cells(6, 3).Value = "square"
ExcelworksheetTwo.Cells(6, 4).Value = "Describtion"


With ExcelworksheetTwo
     
    With ExcelworksheetTwo.Range(Cells(6, 1), Cells(7, 6)).Borders
        .LineStyle = lxcontinuous
        .Weight = xlThin
        .color = black
    End With

Dim y As Integer
    For y = 1 To 3
        With ExcelworksheetTwo.Range(Cells(y, 1), Cells(y, 6))
            .HorizontalAlignment = xlCenter
            .VerticalAlignment = xlCenter
            .Merge
            .Font.Size = 16
            .Font.Name = "Times new roman"
            .Font.Bold = True
            .WrapText = True
        End With
    
    Next y
End With

With ActiveWindow
.SplitColumn = 0
.SplitRow = 6
End With
ActiveWindow.FreezePanes = True

'Bar Schedule Excel Sheet
Set ExcelworksheetThree = workbk.Worksheets.Add
ExcelworksheetThree.Activate

ExcelworksheetThree.Cells(1, 1).Value = company
ExcelworksheetThree.Cells(2, 1).Value = project
ExcelworksheetThree.Cells(3, 1).Value = "Bar Schedule"
ExcelworksheetThree.Cells(4, 1).Value = "Site_No"
ExcelworksheetThree.Cells(4, 2).Value = site
ExcelworksheetThree.Cells(4, 16).Value = "Date"
ExcelworksheetThree.Cells(4, 17).Value = date_no
ExcelworksheetThree.Cells(6, 1).Value = "Bar No."
ExcelworksheetThree.Cells(6, 2).Value = "Location"
ExcelworksheetThree.Cells(6, 4).Value = "Mark"
ExcelworksheetThree.Cells(6, 5).Value = "No of bars"
ExcelworksheetThree.Cells(6, 6).Value = "Diameter"
ExcelworksheetThree.Cells(6, 7).Value = "Length(mm)"
ExcelworksheetThree.Cells(6, 8).Value = "No of member"
ExcelworksheetThree.Cells(6, 9).Value = "Length of reinforcement (m)"
ExcelworksheetThree.Cells(6, 19).Value = "Remark"
ExcelworksheetThree.Cells(7, 9).Value = "Ø6"
ExcelworksheetThree.Cells(7, 10).Value = "Ø8"
ExcelworksheetThree.Cells(7, 11).Value = "Ø10"
ExcelworksheetThree.Cells(7, 12).Value = "Ø12"
ExcelworksheetThree.Cells(7, 13).Value = "Ø14"
ExcelworksheetThree.Cells(7, 14).Value = "Ø16"
ExcelworksheetThree.Cells(7, 15).Value = "Ø20"
ExcelworksheetThree.Cells(7, 16).Value = "Ø24"
ExcelworksheetThree.Cells(7, 17).Value = "Ø32"
ExcelworksheetThree.Cells(7, 18).Value = "Ø40"
ExcelworksheetThree.Cells(10, 6).Value = "Total Length(m)"
ExcelworksheetThree.Cells(11, 6).Value = "Unit Weight(Kg/m)"
ExcelworksheetThree.Cells(12, 6).Value = "Total Weight (Kg)"
ExcelworksheetThree.Cells(13, 6).Value = "Grand Total (Kg)"

   'Create a border on the sheet
With ExcelworksheetThree.Range(Cells(6, 1), Cells(13, 19)).Borders
.LineStyle = lxcontinuous
.Weight = xlThin
.color = black
End With

 ' erase the border on the place where we don't want
With ExcelworksheetThree.Range(Cells(11, 1), Cells(15, 5)).Borders
.LineStyle = xlNone
End With
Dim i As Integer
For i = 1 To 3
    With ExcelworksheetThree.Range(Cells(i, 1), Cells(i, 19))
    .HorizontalAlignment = xlCenter
    .VerticalAlignment = xlCenter
    .Merge
    .Font.Size = 16
    .Font.Name = "Times new roman"
    .Font.Bold = True
    .WrapText = True
    End With
    Next i

Dim j As Integer
For j = 1 To 8
    With ExcelworksheetThree.Range(Cells(6, j), Cells(7, j))
    .HorizontalAlignment = xlCenter
    .VerticalAlignment = xlCenter
    .Merge
    .Font.Size = 12
    .Font.Name = "Times new roman"
    .WrapText = True
    End With
    Next j
    
With ExcelworksheetThree.Range(Cells(6, 9), Cells(6, 18))
    .HorizontalAlignment = xlCenter
    .VerticalAlignment = xlCenter
    .Merge
    .Font.Size = 12
    .Font.Name = "Times new roman"
    .WrapText = True
    End With
    
Dim S As Integer
For S = 10 To 13
    With ExcelworksheetThree.Range(Cells(S, 6), Cells(S, 8))
    .HorizontalAlignment = xlCenter
    .VerticalAlignment = xlCenter
    .Merge
    .Font.Size = 12
    .Font.Name = "Times new roman"
    .WrapText = True
    End With
    Next S
    
 With ExcelworksheetThree.Range(Cells(13, 9), Cells(13, 18))
    .HorizontalAlignment = xlCenter
    .VerticalAlignment = xlCenter
    .Merge
    .Font.Size = 12
    .Font.Name = "Times new roman"
    .Font.Bold = True
    .WrapText = True
    End With
    
With ActiveWindow
.SplitColumn = 0
.SplitRow = 7
End With
ActiveWindow.FreezePanes = True

    'Start the computations
'Variables for the concrete work
Dim row As Integer, rowThree As Integer, CntName As Integer, rowName As Integer
row = 7
rowThree = 7
rowFour = 8
rowName = 7
CntName = 0

Dim CntC As Integer
    CntC = 0

'Variables for the formwork
Dim rowForm As Integer, rowForm2 As Integer
rowForm = 7
rowForm2 = 7

Dim CntF As Integer
    CntF = 6

Dim StrtClmn As Double
Dim ClsClmn As Double
Dim ClmnRunOnes As Integer
    ClmnRunOnes = 0

'Variables for the Bar Schedule
Dim rowBar As Integer
Dim rowBarTwo As Integer
Dim rowBarThree As Integer
Dim rowBarName As Integer
Dim CntBarName As Integer

'Dim V As Integer
Dim RowInsert As Integer
Dim Length() As String
Dim NoOfBar() As String
Dim NoOfBar2() As String
Dim Diameter() As String
RowInsert = 0
rowBar = 8
rowBar2 = 8
rowBarTwo = 8
rowBarThree = 2
rowBarName = 8

Dim CntB As Integer
    CntB = 0 'to count the number of data the user selected - BAR SCHEDULE
    
Dim MystringC As String
Dim Mystring1C As String
Dim MyArrayC() As String
Dim MyArray1C() As String

'Variables for stirrup
Dim NoOfStirrup As Integer
    NoOfStirrup = 0
Dim CntS As Integer
    CntS = 0
Dim StLength As Double
Dim StLengthOfSpan As Double
Dim StDiameter As Double
Dim StSpacing As Double

Dim MyArrayS() As String

Dim rowstirrup As Integer
    rowstirrup = 8

Dim StRowInsert As Integer
    StRowInsert = 0

tryagain:
    With ThisDrawing
        On Error Resume Next
        .SelectionSets("CurrentSelection").Delete

        Set UsersSelection = .SelectionSets.Add("CurrentSelection")
        UsersSelection.SelectOnScreen
        .Application.EnableCancelKey = True
        
        For Each EntitySelected In UsersSelection
            If TypeOf EntitySelected Is AcadDimension Then
                If CntS = 0 Then
                    CntC = CntC + 4
                    CntF = CntF + 6
                Else
                End If
            End If
        Next
    
       'adding additional rows based on comming data
        Dim m As Integer 'm represents the number of the row
        For m = 8 To (6 + CntC)
            With Excelworksheet.Rows(m).Insert
            End With
        Next m
        .Application.ScreenUpdating = True
        
        'adding additional rows based on comming data for formwork
        Dim X As Integer
        For X = 7 To CntF
            With ExcelworksheetTwo.Rows(X).Insert  'inserts one row above 'x'
            End With
        Next X
        .Application.ScreenUpdating = True
    
        For Each EntitySelected In UsersSelection
            If TypeOf EntitySelected Is AcadDimension Then
                If CntS = 0 Then
                
                    CntName = CntName + 4
                    
                    Do While RunOnes < 1
                        With ThisDrawing.Utility
                        Width = .GetReal(Prompt:="Please enter the WIDTH (in Meters) for the beam With the name" & vbCrLf & MyArrayC(2)) 'Recieves the Width from the user
                        Depth = .GetReal(Prompt:="Please enter the DEPTH (in Meters) for the beam With the name" & vbCrLf & MyArrayC(2)) 'Recieves the depth from the user
                        StrtClmn = .GetReal(Prompt:="Please enter the WIDTH of the START COLUMN(m) for the beam With the name" & vbCrLf & MyArrayC(2)) 'Recieves the width of the start column of the beam being currently exported from the user, to add to the formwork and concrete because what the user selected was c/c distance
                        ClsClmn = .GetReal(Prompt:="Please enter the WIDTH of the END COLUMN(m) for the beam With the name" & vbCrLf & MyArrayC(2)) 'Recieves the width of the end column of the beam being currently exported from the user
                        
                        RunOnes = RunOnes + 1
                        'ClmnRunOnes = ClmnRunOnes + 1
                        'Increse both by one so it wont execute again until a new beam name is found
                        End With
                    Loop
                    Excelworksheet.Range("B" & CInt(rowThree)).Value = EntitySelected.Measurement / 1000 + (StrtClmn / 2) 'Print out the Length from the dimension line the user selected then add half of the start column width only to the first span of the beam
                
                    Excelworksheet.Range("B" & CInt(row + 1)).Value = Width 'Print out the depth and width
                    Excelworksheet.Range("B" & CInt(row + 2)).Value = Depth
                    
                    Excelworksheet.Range("C" & CInt(row + 3)).Value = Excelworksheet.Range("B" & CInt(row + 1)).Value * Excelworksheet.Range("B" & CInt(row + 2)).Value * Excelworksheet.Range("B" & CInt(rowThree)).Value
                   'Calculate the volume of the concrete
                    Excelworksheet.Range("D" & CInt(row + 3)).Value = "m^3"
                
                    row = row + 4
                    rowThree = rowThree + 4
                
                   'formwork
            
                    ExcelworksheetTwo.Range("D" & CInt(rowForm)).Value = Excelworksheet.Range("D" & CInt(rowForm2)).Value
            
                    ExcelworksheetTwo.Range("A" & CInt(rowForm)).Value = 2
                    ExcelworksheetTwo.Range("B" & CInt(rowForm)).Value = (Excelworksheet.Range("B" & CInt(rowForm2)).Value)
                    ExcelworksheetTwo.Range("B" & CInt(rowForm + 1)).Value = Excelworksheet.Range("B" & CInt(rowForm2 + 2)).Value
                    ExcelworksheetTwo.Range("C" & CInt(rowForm + 2)).Value = ExcelworksheetTwo.Range("B" & CInt(rowForm)).Value * ExcelworksheetTwo.Range("B" & CInt(rowForm + 1)).Value * ExcelworksheetTwo.Range("A" & CInt(rowForm)).Value
                  'Calculate the volume of the concrete
                    ExcelworksheetTwo.Range("D" & CInt(rowForm + 2)).Value = "m^2"
        
                    ExcelworksheetTwo.Range("A" & CInt(rowForm + 3)).Value = 1
                    ExcelworksheetTwo.Range("B" & CInt(rowForm + 3)).Value = (Excelworksheet.Range("B" & CInt(rowForm2)).Value)
                    ExcelworksheetTwo.Range("B" & CInt(rowForm + 4)).Value = Excelworksheet.Range("B" & CInt(rowForm2 + 1)).Value
                    ExcelworksheetTwo.Range("C" & CInt(rowForm + 5)).Value = ExcelworksheetTwo.Range("B" & CInt(rowForm + 3)).Value * ExcelworksheetTwo.Range("B" & CInt(rowForm + 4)).Value * ExcelworksheetTwo.Range("A" & CInt(rowForm + 3)).Value
                 'Calculate the volume of the concrete
            
                    ExcelworksheetTwo.Range("D" & CInt(rowForm + 5)).Value = "m^2"
                    rowForm = rowForm + 6
                    rowForm2 = rowForm2 + 4
                    StrtClmn = 0
                    
                Else
                    
                    rowstirrup = rowstirrup + CntB + NoOfStirrup
                    
                    StString = EntitySelected.TextOverride
                    StLengthOfSpan = EntitySelected.Measurement
                    
                    For Each tsep In Array("dia", "DIA", "d", "-", ";", "}", "c", "C", vbCr)
                        StString = Replace(StString, tsep, "$")
                    Next tsep
                    
                    StString = Trim(StString)
                    MyArrayS = Split(StString, "$")
                    StDiameter = MyArrayS(1)
                    StSpacing = MyArrayS(3)
                    
                    Do While StRunOnes < 1
                        With ThisDrawing.Utility
                        ConcreteCover = .GetReal(Prompt:="Please enter the CONCRETE COVER (in mm) for the beam With the name" & vbCrLf & BarName) 'Recieves the Concrete cover from the user
                        StRunOnes = StRunOnes + 1
                       
                        End With
                    Loop
                    
                    
                    StLenght = 2 * (Depth - 2 * (ConcreteCover / 1000)) + (2 * (Width - 2 * (ConcreteCover / 1000))) + (2 * (10 * StDiameter / 1000)) 'Calculate the stirrup length with the formula L = 2(D - 2C) + 2(W-2C) + 2*10D
                    StNoOfBar = (StLengthOfSpan / StSpacing) + 1
                    StNoOfBar = WorksheetFunction.RoundUp(StNoOfBar, 0)
                    
                    Dim E As Integer
                    
                    If rowBarTwo > 9 Then
                        For E = (rowBarTwo) To (rowBarTwo)
                            With ExcelworksheetThree.Rows(E).Insert
                            End With
                        Next E
                    End If
                    .Application.ScreenUpdating = True
                    'Print out the values of the stirrup
                     ExcelworksheetThree.Range("B" & CInt(rowBarTwo)).Value = "Stirrup"
                     ExcelworksheetThree.Range("E" & CInt(rowBarTwo)).Value = StNoOfBar
                     ExcelworksheetThree.Range("F" & CInt(rowBarTwo)).Value = StDiameter
                     ExcelworksheetThree.Range("G" & CInt(rowBarTwo)).Value = StLenght * 1000
                        'Check what diameter the shear rebar is and calculate its total length and place it
                        If ExcelworksheetThree.Range("F" & CInt(rowstirrup)).Value = 6 Then
                            ExcelworksheetThree.Range("I" & CInt(rowstirrup)).Value = ExcelworksheetThree.Cells(rowBarTwo, 5).Value * ((ExcelworksheetThree.Cells(rowBarTwo, 7).Value) / 1000)
                        ElseIf ExcelworksheetThree.Range("F" & CInt(rowBarTwo)).Value = 8 Then
                            ExcelworksheetThree.Range("J" & CInt(rowBarTwo)).Value = ExcelworksheetThree.Cells(rowBarTwo, 5).Value * ((ExcelworksheetThree.Cells(rowBarTwo, 7).Value) / 1000)
                        ElseIf ExcelworksheetThree.Range("F" & CInt(rowBarTwo)).Value = 10 Then
                            ExcelworksheetThree.Range("K" & CInt(rowBarTwo)).Value = ExcelworksheetThree.Cells(rowBarTwo, 5).Value * ((ExcelworksheetThree.Cells(rowBarTwo, 7).Value) / 1000)
                        ElseIf ExcelworksheetThree.Range("F" & CInt(rowBarTwo)).Value = 12 Then
                            ExcelworksheetThree.Range("L" & CInt(rowBarTwo)).Value = ExcelworksheetThree.Cells(rowBarTwo, 5).Value * ((ExcelworksheetThree.Cells(rowBarTwo, 7).Value) / 1000)
                        ElseIf ExcelworksheetThree.Range("F" & CInt(rowBarTwo)).Value = 14 Then
                            ExcelworksheetThree.Range("M" & CInt(rowBarTwo)).Value = ExcelworksheetThree.Cells(rowBarTwo, 5).Value * ((ExcelworksheetThree.Cells(rowBarTwo, 7).Value) / 1000)
                        ElseIf ExcelworksheetThree.Range("F" & CInt(rowBarTwo)).Value = 16 Then
                            ExcelworksheetThree.Range("N" & CInt(rowBarTwo)).Value = ExcelworksheetThree.Cells(rowBarTwo, 5).Value * ((ExcelworksheetThree.Cells(rowBarTwo, 7).Value) / 1000)
                        ElseIf ExcelworksheetThree.Range("F" & CInt(rowBarTwo)).Value = 20 Then
                            ExcelworksheetThree.Range("O" & CInt(rowBarTwo)).Value = ExcelworksheetThree.Cells(rowBarTwo, 5).Value * ((ExcelworksheetThree.Cells(rowBarTwo, 7).Value) / 1000)
                        ElseIf ExcelworksheetThree.Range("F" & CInt(rowBarTwo)).Value = 24 Then
                            ExcelworksheetThree.Range("P" & CInt(rowBarTwo)).Value = ExcelworksheetThree.Cells(rowBarTwo, 5).Value * ((ExcelworksheetThree.Cells(rowBarTwo, 7).Value) / 1000)
                        ElseIf ExcelworksheetThree.Range("F" & CInt(rowBarTwo)).Value = 30 Then
                            ExcelworksheetThree.Range("q" & CInt(rowBarTwo)).Value = ExcelworksheetThree.Cells(rowBarTwo, 5).Value * ((ExcelworksheetThree.Cells(rowBarTwo, 7).Value) / 1000)
                        ElseIf ExcelworksheetThree.Range("F" & CInt(rowBarTwo)).Value = 40 Then
                            ExcelworksheetThree.Range("r" & CInt(rowBarTwo)).Value = ExcelworksheetThree.Cells(rowBarTwo, 5).Value * ((ExcelworksheetThree.Cells(rowBarTwo, 7).Value) / 1000)
                    
                        End If
                             
                    
                    rowBarTwo = rowBarTwo + 1
                    NoOfStirrup = NoOfStirrup + 1
                    
                    Dim F As Integer
                    
                    F = 0
                    StCntc = CntC + 6
                    Do While F < 4
                        Excelworksheet.Rows(StCntc - 3).Delete
                        F = F + 1
                    Loop
                    .Application.ScreenUpdating = True
                    
                    Dim G As Integer
                    G = 0
                    Do While G < 7
                        ExcelworksheetTwo.Rows(CntF - 5).Delete
                        G = G + 1
                    Loop
                    .Application.ScreenUpdating = True
                    
                    CntC = CntC - 4
                    CntF = CntF - 6
                    
                End If
                
            Else
             
                MystringC = EntitySelected.TextString
            
                For Each tsep In Array(";", ",", ", ", "-", vbCr)
                    MystringC = Replace(MystringC, tsep, "%%C")
                Next tsep
            
                MystringC = Trim(MystringC)
                MyArrayC = Split(MystringC, "%%C")
               
                If MyArrayC(2) Like "*Beam*" Then
                    rowName = rowName + CntName
                    Excelworksheet.Range("D" & CInt(rowName)).Value = MyArrayC(2)
                    Excelworksheet.Range("B" & CInt(rowThree - 4)).Value = (Excelworksheet.Range("B" & CInt(rowThree - 4)).Value) + (ClsClmn / 2)
    
                    RunOnes = 0
                    CntName = 0
                    
                    BarName = MyArrayC(2)
                    CntBarName = 0
                    CntS = 0
                    'ClmnRunOnes = 0 'Set ClmnRunOnes back to zero when we encounter another beam name, which means the user has started selecting a new beam
                
                Else
                    CntB = CntB + 1
                    CntS = CntS + 1

                    Dim V As Integer
                    'adding additional rowBars based on comming data
                    
                    If rowBarTwo > 9 Then
                        For V = (rowBarTwo) To (rowBarTwo)
                            With ExcelworksheetThree.Rows(V).Insert
                            End With
                        Next V
                    End If
                    .Application.ScreenUpdating = True
                    
                    Do While CntBarName < 1
                        ExcelworksheetThree.Range("B" & CInt(rowBarName + NoOfStirrup)).Value = BarName 'Print out the beam name
                        CntBarName = CntBarName + 1
                    Loop
                    
                    ExcelworksheetThree.Range("A" & CInt(rowBar2 + NoOfStirrup)).Value = CInt(rowBarThree) - 1
                    rowBarThree = rowBarThree + 1
                    rowBar2 = rowBar2 + 1
                
                'Remove any double spaces
                    For Each tsep In Array("dia", "DIA", "d", " L=", "L=", "%%C", "-", ";", "}", vbCr)
                        MystringC = Replace(MystringC, tsep, "%%C")
                    Next tsep
                'Remove any leading or trailing spaces
                    MystringC = Trim(MystringC)
                'Use Split function to divide up the component parts of the string
                    MyArray = Split(MystringC, "%%C")
                    If IsNumeric(MyArray(0)) = False Then
                                                        
                     'Check if myarray actually has values
                        For k = 0 To UBound(MyArray) - 2
                            ExcelworksheetThree.Cells(rowBarTwo, k + 5).Value = MyArray(k + 1)
                    
         'sumation of length under each diameter calculation
         'summation of length=No of bar*Length
         
                            If ExcelworksheetThree.Range("F" & CInt(rowBarTwo)).Value = 6 Then
                                ExcelworksheetThree.Range("I" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 8 Then
                                ExcelworksheetThree.Range("J" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 10 Then
                                ExcelworksheetThree.Range("K" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 12 Then
                                ExcelworksheetThree.Range("L" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 14 Then
                                ExcelworksheetThree.Range("M" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 16 Then
                                ExcelworksheetThree.Range("N" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 20 Then
                                ExcelworksheetThree.Range("O" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 24 Then
                                ExcelworksheetThree.Range("P" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 30 Then
                                ExcelworksheetThree.Range("q" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 40 Then
                                ExcelworksheetThree.Range("r" & CInt(rowBarTwo)).Value = ExcelworksheetThree.Cells(rowBarTwo, 5).Value * ((ExcelworksheetThree.Cells(rowBarTwo, 7).Value) / 1000)
                    
                            End If
                            
                        Next k
                    Else
                        For k = 0 To UBound(MyArray) 'If the userselction does not have those preceeding & trailing characters, it executes the following loop
                            Cells(rowBarTwo, k + 5).Value = MyArray(k)
                    
                            If ExcelworksheetThree.Range("F" & CInt(rowBarTwo)).Value = 6 Then
                                ExcelworksheetThree.Range("I" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 8 Then
                                ExcelworksheetThree.Range("J" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 10 Then
                                ExcelworksheetThree.Range("K" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 12 Then
                                ExcelworksheetThree.Range("L" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 14 Then
                                ExcelworksheetThree.Range("M" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 16 Then
                                ExcelworksheetThree.Range("N" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 20 Then
                                ExcelworksheetThree.Range("O" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 24 Then
                                ExcelworksheetThree.Range("P" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 32 Then
                                ExcelworksheetThree.Range("q" & CInt(rowBarTwo)).Value = ExcelworksheetThree.Cells(rowBarTwo, 5).Value * ((ExcelworksheetThree.Cells(rowBarTwo, 7).Value) / 1000)
                            ElseIf ExcelworksheetThree.Range("F" & CInt(rowBarTwo)).Value = 40 Then
                                ExcelworksheetThree.Range("r" & CInt(rowBarTwo)).Value = ExcelworksheetThree.Cells(rowBarTwo, 5).Value * ((ExcelworksheetThree.Cells(rowBarTwo, 7).Value) / 1000)
                
                            End If
                            
                        Next k
                    
                    End If 'End If IsNumeric
               
                rowBarTwo = rowBarTwo + 1 '
                rowBarName = rowBarName + 1
                StRunOnes = 0
                End If 'End the if command that says If my array is like "beam"
    
            End If 'Ends the command that says If type of entity selected is Acaddimension
                
        Next 'Next For each entity selected
    'calculate the total volume of concrete
      Excelworksheet.Range("C" & CInt(CntC + 7)).Value = WorksheetFunction.Sum(Range(Excelworksheet.Cells(7, 3), Excelworksheet.Cells((CntC + 6), 3))) 'Calculate the sum of the concrete work
    
    End With
'Formwork
ExcelworksheetTwo.Range("C" & CInt(CntF + 1)).Value = WorksheetFunction.Sum(Range(ExcelworksheetTwo.Cells(9, 3), ExcelworksheetTwo.Cells((CntF), 3))) 'Calculate the sum of the formworks exported
ExcelworksheetTwo.Range("D" & CInt(CntF + 1)).Value = "Total Area (m^2)" 'Give the description that the sum of the formwork areas is in square meters
  
If RunOnes > 0 Then
    Excelworksheet.Range("B" & CInt(rowThree - 4)).Value = (Excelworksheet.Range("B" & CInt(rowThree - 4)).Value) + (ClsClmn / 2) 'Add half of the end column to the last length
    ExcelworksheetTwo.Range("B" & CInt(rowForm - 3)).Value = (ExcelworksheetTwo.Range("B" & CInt(rowForm - 3)).Value) + (ClsClmn / 2) '
    ExcelworksheetTwo.Range("B" & CInt(rowForm - 6)).Value = (ExcelworksheetTwo.Range("B" & CInt(rowForm - 6)).Value) + (ClsClmn / 2) '
End If

 Excelworksheet.Activate
Dim T As Integer 'For the concrete work
 For T = 4 To CntC + 7
     With Excelworksheet.Range(Cells(T, 1), Cells(T, 6))
          .HorizontalAlignment = xlCenter
          .VerticalAlignment = xlCenter
          .Font.Size = 12
          .Font.Name = "Times new roman"
          .Application.ScreenUpdating = True
          End With
        Next T
        
Dim U As Integer 'For the concrete Work
 For U = 6 To CntC + 7
    With Excelworksheet.Range(Cells(U, 4), Cells(U, 6))
    .HorizontalAlignment = xlCenter
    .VerticalAlignment = xlCenter
    .Merge
    .Font.Size = 12
    .Font.Name = "Times new roman"
    .WrapText = True
    .Application.ScreenUpdating = True
    End With
  Next U

 ExcelworksheetTwo.Activate
Dim W As Integer 'For the Formwork
 For W = 4 To (CntF + 1)
     With ExcelworksheetTwo.Range(Cells(W, 1), Cells(W, 6))
          .HorizontalAlignment = xlCenter
          .VerticalAlignment = xlCenter
          .Font.Size = 12
          .Font.Name = "Times new roman"
          .Application.ScreenUpdating = True
          End With
        Next W
        
Dim H As Integer 'For the FormWork
 For H = 6 To (CntF + 1)
    With ExcelworksheetTwo.Range(Cells(H, 4), Cells(H, 6))
    .HorizontalAlignment = xlCenter
    .VerticalAlignment = xlCenter
    .Merge
    .Font.Size = 12
    .Font.Name = "Times new roman"
    .WrapText = True
    .Application.ScreenUpdating = True
    End With
  Next H

'Bar Schedule
CntB = (rowBarTwo - 8)

ExcelworksheetThree.Activate
Dim R As Integer 'For the Bar schedule
 For R = 6 To (CntB + 7)
    With ExcelworksheetThree.Range(Cells(R, 2), Cells(R, 3))
    .HorizontalAlignment = xlCenter
    .VerticalAlignment = xlCenter
    .Merge
    .Font.Size = 12
    .Font.Name = "Times new roman"
    .WrapText = True
    .Application.ScreenUpdating = True
    End With
  Next R

    ExcelworksheetThree.Range("I" & CInt(CntB + 8)).Value = WorksheetFunction.Sum(Range(ExcelworksheetThree.Cells(8, 9), ExcelworksheetThree.Cells((CntB + 7), 9)))
    ExcelworksheetThree.Range("J" & CInt(CntB + 8)).Value = WorksheetFunction.Sum(Range(ExcelworksheetThree.Cells(8, 10), ExcelworksheetThree.Cells((CntB + 7), 10)))
    ExcelworksheetThree.Range("K" & CInt(CntB + 8)).Value = WorksheetFunction.Sum(Range(ExcelworksheetThree.Cells(8, 11), ExcelworksheetThree.Cells((CntB + 7), 11)))
    ExcelworksheetThree.Range("L" & CInt(CntB + 8)).Value = WorksheetFunction.Sum(Range(ExcelworksheetThree.Cells(8, 12), ExcelworksheetThree.Cells((CntB + 7), 12)))
    ExcelworksheetThree.Range("M" & CInt(CntB + 8)).Value = WorksheetFunction.Sum(Range(ExcelworksheetThree.Cells(8, 13), ExcelworksheetThree.Cells((CntB + 7), 13)))
    ExcelworksheetThree.Range("N" & CInt(CntB + 8)).Value = WorksheetFunction.Sum(Range(ExcelworksheetThree.Cells(8, 14), ExcelworksheetThree.Cells((CntB + 7), 14)))
    ExcelworksheetThree.Range("O" & CInt(CntB + 8)).Value = WorksheetFunction.Sum(Range(ExcelworksheetThree.Cells(8, 15), ExcelworksheetThree.Cells((CntB + 7), 15)))
    ExcelworksheetThree.Range("P" & CInt(CntB + 8)).Value = WorksheetFunction.Sum(Range(ExcelworksheetThree.Cells(8, 16), ExcelworksheetThree.Cells((CntB + 7), 16)))
    ExcelworksheetThree.Range("q" & CInt(CntB + 8)).Value = WorksheetFunction.Sum(Range(ExcelworksheetThree.Cells(8, 17), ExcelworksheetThree.Cells((CntB + 7), 17)))
    ExcelworksheetThree.Range("r" & CInt(CntB + 8)).Value = WorksheetFunction.Sum(Range(ExcelworksheetThree.Cells(8, 18), ExcelworksheetThree.Cells((CntB + 7), 18)))
            
            'assigning unit weight for each rebar diameter in excel cells
            'W=D^2*(1/162)
    ExcelworksheetThree.Range("I" & CInt(CntB + 9)).Value = 0.222
    ExcelworksheetThree.Range("J" & CInt(CntB + 9)).Value = 0.395
    ExcelworksheetThree.Range("K" & CInt(CntB + 9)).Value = 0.617
    ExcelworksheetThree.Range("L" & CInt(CntB + 9)).Value = 0.888
    ExcelworksheetThree.Range("M" & CInt(CntB + 9)).Value = 1.208
    ExcelworksheetThree.Range("N" & CInt(CntB + 9)).Value = 1.578
    ExcelworksheetThree.Range("O" & CInt(CntB + 9)).Value = 2.467
    ExcelworksheetThree.Range("P" & CInt(CntB + 9)).Value = 3.552
    ExcelworksheetThree.Range("q" & CInt(CntB + 9)).Value = 6.321
    ExcelworksheetThree.Range("r" & CInt(CntB + 9)).Value = 9.876
            
            'calculation of total weight for each rebar diameter
            'total weight=total length*unit weight
    ExcelworksheetThree.Range("I" & CInt(CntB + 10)).Value = ExcelworksheetThree.Cells(CntB + 8, 9).Value * ExcelworksheetThree.Cells(CntB + 9, 9).Value
    ExcelworksheetThree.Range("J" & CInt(CntB + 10)).Value = ExcelworksheetThree.Cells(CntB + 8, 10).Value * ExcelworksheetThree.Cells(CntB + 9, 10).Value
    ExcelworksheetThree.Range("K" & CInt(CntB + 10)).Value = ExcelworksheetThree.Cells(CntB + 8, 11).Value * ExcelworksheetThree.Cells(CntB + 9, 11).Value
    ExcelworksheetThree.Range("L" & CInt(CntB + 10)).Value = ExcelworksheetThree.Cells(CntB + 8, 12).Value * ExcelworksheetThree.Cells(CntB + 9, 12).Value
    ExcelworksheetThree.Range("M" & CInt(CntB + 10)).Value = ExcelworksheetThree.Cells(CntB + 8, 13).Value * ExcelworksheetThree.Cells(CntB + 9, 13).Value
    ExcelworksheetThree.Range("N" & CInt(CntB + 10)).Value = ExcelworksheetThree.Cells(CntB + 8, 14).Value * ExcelworksheetThree.Cells(CntB + 9, 14).Value
    ExcelworksheetThree.Range("O" & CInt(CntB + 10)).Value = ExcelworksheetThree.Cells(CntB + 8, 15).Value * ExcelworksheetThree.Cells(CntB + 9, 15).Value
    ExcelworksheetThree.Range("P" & CInt(CntB + 10)).Value = ExcelworksheetThree.Cells(CntB + 8, 16).Value * ExcelworksheetThree.Cells(CntB + 9, 16).Value
    ExcelworksheetThree.Range("q" & CInt(CntB + 10)).Value = ExcelworksheetThree.Cells(CntB + 8, 17).Value * ExcelworksheetThree.Cells(CntB + 9, 17).Value
    ExcelworksheetThree.Range("r" & CInt(CntB + 10)).Value = ExcelworksheetThree.Cells(CntB + 8, 18).Value * ExcelworksheetThree.Cells(CntB + 9, 18).Value
            
            'calculation of Grand total
            'Grand total=sumation of the total weight
    ExcelworksheetThree.Range("I" & CInt(CntB + 11)).Value = WorksheetFunction.Sum(Range(ExcelworksheetThree.Cells((CntB + 10), 9), ExcelworksheetThree.Cells((CntB + 10), 18)))
    Exit Sub
Here:
MsgBox "AN error has occured; please close the opened excel, RESET the program and start export again"
End Sub

Private Sub site_Change()
If Not IsNumeric(site.Value) Then 'to make the text box accept only number
               MsgBox "Only numbers are allowed"
      End If
End Sub
